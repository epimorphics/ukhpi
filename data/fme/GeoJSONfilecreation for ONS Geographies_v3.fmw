FME workspace GeoJSONfilecreation for ONS Geographies_v3.fmw

Parameters:
- SourceDataset_ESRISHAPE = $(FME_MF_DIR)Input Data/Regions_December_2016_Ultra_Generalised_Clipped_Boundaries_in_England/Regions_December_2016_Ultra_Generalised_Clipped_Boundaries_in_England.shp   # Source Esri Shapefile(s)
- SourceDataset_ESRISHAPE_9 = $(FME_MF_DIR)Input Data/Local_Authority_Districts_December_2016_Ultra_Generalised_Clipped_Boundaries_in_Great_Britain/Local_Authority_Districts_December_2016_Ultra_Generalised_Clipped_Boundaries_in_Great_Britain.shp   # Source Esri Shapefile(s)
- SourceDataset_ESRISHAPE_11 = $(FME_MF_DIR)Input Data/Countries_December_2016_Ultra_Generalised_Clipped_Boundaries_in_Great_Britain/Countries_December_2016_Ultra_Generalised_Clipped_Boundaries_in_Great_Britain.shp   # Source Esri Shapefile(s)
- SourceDataset_ESRISHAPE_10 = $(FME_MF_DIR)Input Data/Counties_December_2016_Ultra_Generalised_Clipped_Boundaries_in_England/Counties_December_2016_Ultra_Generalised_Clipped_Boundaries_in_England.shp   # Source Esri Shapefile(s)
- SourceDataset_ESRISHAPE_12 = $(FME_MF_DIR)Input Data/Counties_and_Unitary_Authorities_December_2016_Ultra_Generalised_Clipped_Boundaries_in_England_and_Wales/Counties_and_Unitary_Authorities_December_2016_Ultra_Generalised_Clipped_Boundaries_in_England_and_Wales.shp   # Source Esri Shapefile(s)
- SourceDataset_ESRISHAPE_14 = $(FME_MF_DIR)Input Data/Combined_Authorities_March_2017_Ultra_Generalised_Clipped_Boundaries_in_England/Combined_Authorities_March_2017_Ultra_Generalised_Clipped_Boundaries_in_England.shp   # Source Esri Shapefile(s)
- DestDataset_GEOJSON = $(FME_MF_DIR_USERTYPED)Outputs/A1b.json   # Destination GeoJSON File

Readers:
- ESRISHAPE_1: ESRISHAPE from $(SourceDataset_ESRISHAPE)
- ESRISHAPE_2: ESRISHAPE from $(SourceDataset_ESRISHAPE_9)
- ESRISHAPE_3: ESRISHAPE from $(SourceDataset_ESRISHAPE_11)
- ESRISHAPE_4: ESRISHAPE from $(SourceDataset_ESRISHAPE_10)
- ESRISHAPE_5: ESRISHAPE from $(SourceDataset_ESRISHAPE_12)
- ESRISHAPE_6: ESRISHAPE from $(SourceDataset_ESRISHAPE_14)

Writers:
- GEOJSON_1: GEOJSON to $(DestDataset_GEOJSON)

Note: ONS Input data (latest) / note use ultra-generalised versions / Form / http://geoportal.statistics.gov.uk/
Note: disabled counties-england as duplated in counties-and-unitary-authorities
Counties_December_2016_Ultra_Generalised_Clipped_Boundaries_in_England (reader ESRISHAPE_4) [off]
    attributes: objectid long, cty16cd char(80), cty16nm char(80), bng_e long, bng_n long, long number(24,15), lat number(24,15), st_areasha number(24,15), st_lengths number(24,15)
    -> Reprojector
Note: Reproject from OSGB to WGS84
Reprojector
    RASTER_CELL_SIZE = Preserve Cells
    INTERPOLATION_TYPE_NAME = Nearest Neighbor
    SOURCE = BritishNatGrid
    DEST = EPSG:4326
    REPROJECTED -> 2DForcer
Note: remove any 3d elements
2DForcer
    2D -> CoordinateRounder
Note: Round coordinates to 6 d.ps
CoordinateRounder
    ZPREC = 0
    YPREC = 6
    XPREC = 6
    ROUNDED -> AttributeRemover
Note: Remove not needed attributes
AttributeRemover
    REMOVE_ATTRS = bng_n,long,st_areasha,lat,bng_e,st_lengths,objectid
    -> AttributeRenamer
Note: Rename attributes to common set: / name / welsh-name / code
AttributeRenamer
    ATTR_TABLE:
      RENAME_SET_DEFAULT cty16nm > name
      RENAME_SET_DEFAULT cty16cd > code
    -> AttributeCreator
Note: create and set tag attributes: / type / year
AttributeCreator
    ATTR_TABLE:
      SET_TO type = counties-england
      SET_TO year = 2016
    -> Generalizer_7
Note: further generalize data... / using Deveau method
Generalizer_7
    TOLERANCE = 0.01
    ANGLE = 110
    PRESERVE = Yes
    ALG_TEXT = Deveau (Generalize)
    NUMWEDGES = 1
    -> CoordinateRounder_12
Note: coordinate rounder to 4 decimal places
CoordinateRounder_12
    ZPREC = 0
    YPREC = 4
    XPREC = 4
    ROUNDED -> A1c-test (writer GEOJSON_1)
Regions_December_2016_Ultra_Generalised_Clipped_Boundaries_in_England (reader ESRISHAPE_1)
    attributes: objectid long, rgn16cd char(80), rgn16nm char(80), bng_e long, bng_n long, long number(24,15), lat number(24,15), st_areasha number(24,15), st_lengths number(24,15)
    -> Reprojector_2
Reprojector_2
    RASTER_CELL_SIZE = Preserve Cells
    INTERPOLATION_TYPE_NAME = Nearest Neighbor
    SOURCE = BritishNatGrid
    DEST = EPSG:4326
    REPROJECTED -> 2DForcer_2
2DForcer_2
    2D -> CoordinateRounder_2
CoordinateRounder_2
    ZPREC = 0
    YPREC = 6
    XPREC = 6
    ROUNDED -> AttributeRemover_2
AttributeRemover_2
    REMOVE_ATTRS = bng_n,long,st_areasha,lat,bng_e,st_lengths,objectid
    -> AttributeRenamer_2
AttributeRenamer_2
    ATTR_TABLE:
      RENAME_SET_DEFAULT rgn16nm > name
      RENAME_SET_DEFAULT rgn16cd > code
    -> AttributeCreator_2
AttributeCreator_2
    ATTR_TABLE:
      SET_TO type = regions-england
      SET_TO year = 2016
    -> Generalizer_6
Generalizer_6
    TOLERANCE = 0.015
    ANGLE = 110
    PRESERVE = Yes
    ALG_TEXT = Deveau (Generalize)
    NUMWEDGES = 1
    -> CoordinateRounder_11
CoordinateRounder_11
    ZPREC = 0
    YPREC = 4
    XPREC = 4
    ROUNDED -> A1c-test (writer GEOJSON_1)
Counties_and_Unitary_Authorities_December_2016_Ultra_Generalised_Clipped_Boundaries_in_England_and_Wales (reader ESRISHAPE_5)
    attributes: objectid long, ctyua16cd char(80), ctyua16nm char(80), ctyua16nmw char(80), bng_e long, bng_n long, long number(24,15), lat number(24,15), st_areasha number(24,15), st_lengths number(24,15)
    -> Reprojector_7
Reprojector_7
    RASTER_CELL_SIZE = Preserve Cells
    INTERPOLATION_TYPE_NAME = Nearest Neighbor
    SOURCE = BritishNatGrid
    DEST = EPSG:4326
    REPROJECTED -> 2DForcer_7
2DForcer_7
    2D -> CoordinateRounder_7
CoordinateRounder_7
    ZPREC = 0
    YPREC = 6
    XPREC = 6
    ROUNDED -> AttributeRemover_7
AttributeRemover_7
    REMOVE_ATTRS = bng_n,long,st_areasha,lat,bng_e,st_lengths,objectid
    -> AttributeRenamer_7
AttributeRenamer_7
    ATTR_TABLE:
      RENAME_SET_DEFAULT ctyua16nm > name
      RENAME_SET_DEFAULT ctyua16nmw > welsh-name
      RENAME_SET_DEFAULT ctyua16cd > code
    -> AttributeCreator_7
AttributeCreator_7
    ATTR_TABLE:
      SET_TO type = counties-and-unitary-authorities-england-wales
      SET_TO year = 2016
    -> Generalizer_2
Generalizer_2
    TOLERANCE = 0.01
    ANGLE = 110
    PRESERVE = Yes
    ALG_TEXT = Deveau (Generalize)
    NUMWEDGES = 1
    -> CoordinateRounder_5
CoordinateRounder_5
    ZPREC = 0
    YPREC = 4
    XPREC = 4
    ROUNDED -> A1c-test (writer GEOJSON_1)
Combined_Authorities_March_2017_Ultra_Generalised_Clipped_Boundaries_in_England (reader ESRISHAPE_6)
    attributes: objectid long, cauth17cd char(80), cauth17nm char(80), bng_e long, bng_n long, long number(24,15), lat number(24,15), st_areasha number(24,15), st_lengths number(24,15)
    -> Reprojector_6
Reprojector_6
    RASTER_CELL_SIZE = Preserve Cells
    INTERPOLATION_TYPE_NAME = Nearest Neighbor
    SOURCE = BritishNatGrid
    DEST = EPSG:4326
    REPROJECTED -> 2DForcer_6
2DForcer_6
    2D -> CoordinateRounder_6
CoordinateRounder_6
    ZPREC = 0
    YPREC = 6
    XPREC = 6
    ROUNDED -> AttributeRemover_6
AttributeRemover_6
    REMOVE_ATTRS = bng_n,long,st_areasha,lat,bng_e,st_lengths,objectid
    -> AttributeRenamer_6
AttributeRenamer_6
    ATTR_TABLE:
      RENAME_SET_DEFAULT cauth17nm > name
      RENAME_SET_DEFAULT cauth17cd > code
    -> AttributeCreator_6
AttributeCreator_6
    ATTR_TABLE:
      SET_TO type = combined-authorities-england
      SET_TO year = 2017
    -> Generalizer_3
Generalizer_3
    TOLERANCE = 0.01
    ANGLE = 110
    PRESERVE = Yes
    ALG_TEXT = Deveau (Generalize)
    NUMWEDGES = 1
    -> CoordinateRounder_8
CoordinateRounder_8
    ZPREC = 0
    YPREC = 4
    XPREC = 4
    ROUNDED -> A1c-test (writer GEOJSON_1)
Countries_December_2016_Ultra_Generalised_Clipped_Boundaries_in_Great_Britain (reader ESRISHAPE_3)
    attributes: objectid long, ctry16cd char(80), ctry16nm char(80), ctry16nmw char(80), bng_e long, bng_n long, long number(24,15), lat number(24,15), st_areasha number(24,15), st_lengths number(24,15)
    -> Reprojector_4
Reprojector_4
    RASTER_CELL_SIZE = Preserve Cells
    INTERPOLATION_TYPE_NAME = Nearest Neighbor
    SOURCE = BritishNatGrid
    DEST = EPSG:4326
    REPROJECTED -> 2DForcer_4
2DForcer_4
    2D -> CoordinateRounder_4
CoordinateRounder_4
    ZPREC = 0
    YPREC = 6
    XPREC = 6
    ROUNDED -> AttributeRemover_4
AttributeRemover_4
    REMOVE_ATTRS = bng_n,long,st_areasha,lat,bng_e,st_lengths,objectid
    -> AttributeRenamer_4
AttributeRenamer_4
    ATTR_TABLE:
      RENAME_SET_DEFAULT ctry16nm > name
      RENAME_SET_DEFAULT ctry16nmw > welsh-name
      RENAME_SET_DEFAULT ctry16cd > code
    -> AttributeCreator_4
AttributeCreator_4
    ATTR_TABLE:
      SET_TO type = countries-gb
      SET_TO year = 2016
    -> Generalizer_4
Generalizer_4
    TOLERANCE = 0.015
    ANGLE = 110
    PRESERVE = Yes
    ALG_TEXT = Deveau (Generalize)
    NUMWEDGES = 1
    -> CoordinateRounder_9
CoordinateRounder_9
    ZPREC = 0
    YPREC = 4
    XPREC = 4
    ROUNDED -> A1c-test (writer GEOJSON_1)
Local_Authority_Districts_December_2016_Ultra_Generalised_Clipped_Boundaries_in_Great_Britain (reader ESRISHAPE_2)
    attributes: objectid long, lad16cd char(80), lad16nm char(80), lad16nmw char(80), bng_e long, bng_n long, long number(24,15), lat number(24,15), st_areasha number(24,15), st_lengths number(24,15)
    -> Reprojector_3
Reprojector_3
    RASTER_CELL_SIZE = Preserve Cells
    INTERPOLATION_TYPE_NAME = Nearest Neighbor
    SOURCE = BritishNatGrid
    DEST = EPSG:4326
    REPROJECTED -> 2DForcer_3
2DForcer_3
    2D -> CoordinateRounder_3
CoordinateRounder_3
    ZPREC = 0
    YPREC = 6
    XPREC = 6
    ROUNDED -> AttributeRemover_3
AttributeRemover_3
    REMOVE_ATTRS = bng_n,long,st_areasha,lat,bng_e,st_lengths,objectid
    -> AttributeRenamer_3
AttributeRenamer_3
    ATTR_TABLE:
      RENAME_SET_DEFAULT lad16nm > name
      RENAME_SET_DEFAULT lad16nmw > welsh-name
      RENAME_SET_DEFAULT lad16cd > code
    -> AttributeCreator_3
AttributeCreator_3
    ATTR_TABLE:
      SET_TO type = la-districts-gb
      SET_TO year = 2016
    -> Generalizer_5
Generalizer_5
    TOLERANCE = 0.01
    ANGLE = 110
    PRESERVE = Yes
    ALG_TEXT = Deveau (Generalize)
    NUMWEDGES = 1
    -> CoordinateRounder_10
CoordinateRounder_10
    ZPREC = 0
    YPREC = 4
    XPREC = 4
    ROUNDED -> A1c-test (writer GEOJSON_1)
Note: ourput as geoJSON / UTF-8 / pretty-print
A1c-test (writer GEOJSON_1)
    attributes: type string, year string, name string, welsh-name string, code string
